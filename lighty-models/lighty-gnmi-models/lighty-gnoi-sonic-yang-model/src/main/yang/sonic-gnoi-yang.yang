module sonic-gnoi-yang {
    yang-version 1;
    namespace "sonic-gnoi-yang";
    prefix "sonic-gnoi";

    description
        "Model mapping SONiC gNOI Proto file
         https://github.com/Azure/sonic-telemetry/blob/master/proto/gnoi/sonic_gnoi.proto to YANG.

         Copyright (c) 2021 PANTHEON.tech s.r.o. All Rights Reserved.

         This program and the accompanying materials are made available under the
         terms of the Eclipse Public License v1.0 which accompanies this distribution,
         and is available at https://www.eclipse.org/legal/epl-v10.html";

    revision "2021-06-14" {
        description "Initial revision";
    }

    grouping SonicOutput {
        container SonicOutput {
            leaf status {
                type int32;
            }

            leaf status_detail {
                type string;
            }
        }
    }

    grouping TechsupportRequest {
        leaf date {
            type string;
        }
    }

    grouping TechsupportResponse {
        leaf output_filename {
            type string;
        }
    }

    grouping ClearNeighborsRequest {
        leaf force {
            type boolean;
        }

        leaf family {
            type string;
        }

        leaf ip {
            type string;
        }

        leaf ifname {
            type string;
        }
    }

    grouping ClearNeighborsResponse {
        leaf response {
            type string;
        }
    }

    grouping CopyConfigRequest {
        leaf source {
            type string;
        }

        leaf overwrite {
            type boolean;
        }

        leaf destination {
            type string;
        }
    }

    grouping CopyConfigResponse {
        uses SonicOutput;
    }

    grouping ImageInstallRequest {
        leaf imagename {
            type string;
        }
    }

    grouping ImageInstallResponse {
        uses SonicOutput;
    }

    grouping ImageRemoveRequest {
        leaf imagename {
            type string;
        }
    }

    grouping ImageRemoveResponse {
        uses SonicOutput;
    }

    grouping ImageDefaultRequest {
        leaf imagename {
            type string;
        }
    }

    grouping ImageDefaultResponse {
        uses SonicOutput;
    }

    rpc ShowTechsupport {
        input {
            container TechsupportRequest {
                uses TechsupportRequest;
            }
        }
        output {
            container TechsupportResponse {
                uses TechsupportResponse;
            }
        }
    }

    rpc CopyConfig {
        input {
            container CopyConfigRequest {
                uses CopyConfigRequest;
            }
        }
        output {
            container CopyConfigResponse {
                uses CopyConfigResponse;
            }
        }
    }

    rpc ImageInstall {
        input {
            container ImageInstallRequest {
                uses ImageInstallRequest;
            }
        }
        output {
            container ImageInstallResponse {
                uses ImageInstallResponse;
            }
        }
    }

    rpc ImageRemove {
        input {
            container ImageRemoveRequest {
                uses ImageRemoveRequest;
            }
        }
        output {
            container ImageRemoveResponse {
                uses ImageRemoveResponse;
            }
        }
    }

    rpc ImageDefault {
        input {
            container ImageDefaultRequest {
                uses ImageDefaultRequest;
            }
        }
        output {
            container ImageDefaultResponse {
                uses ImageDefaultResponse;
            }
        }
    }

    rpc ClearNeighbors {
        input {
            container ClearNeighborsRequest {
                uses ClearNeighborsRequest;
            }
        }
        output {
            container ClearNeighborsResponse {
                uses ClearNeighborsResponse;
            }
        }
    }

}
